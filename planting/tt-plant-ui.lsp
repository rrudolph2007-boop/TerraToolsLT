;;; Searchable plant manager. Callback state is local to each dialog invocation.
(setq *TT:PlantUIModuleLoaded* T)

(defun TT:PlantUIString (value)
  (cond ((eq (type value) 'STR) value) ((numberp value) (rtos value 2 4)) (T "")))

(defun TT:PlantUISelected ()
  (if (and visible (> (length visible) 0)) (nth (atoi (get_tile "plants")) visible)))

(defun TT:PlantUIKey (record)
  (if (TT:DataValue record 'PROJECT_PLANT_ID) (TT:DataValue record 'PROJECT_PLANT_ID) (TT:DataValue record 'PLANT_ID)))

(defun TT:PlantUIRow (record)
  (strcat (TT:PlantSearchLabel record)
    (if (member (if (TT:DataValue record 'PROJECT_PLANT_ID)
                  (TT:DataValue record 'MASTER_PLANT_ID) (TT:DataValue record 'PLANT_ID)) sample-ids) " | SAMPLE" "")))

(defun TT:PlantUIActionEnabledP (key has-project has-record view)
  (cond ((member key '("variant" "edit" "remove" "place")) (and has-project has-record (= view 0)))
    ((= key "add") (and has-project has-record (/= view 0)))
    ((= key "favorite") (and has-project has-record))
    ((= key "details") has-record)
    ((= key "area") has-project)))

(defun TT:PlantUIDetails (/ record source id added)
  (setq record (TT:PlantUISelected))
  (if record
    (progn
      (set_tile "name" (TT:PlantUIString (TT:DataValue record 'BOTANICAL_NAME)))
      (set_tile "common" (TT:PlantUIString (TT:DataValue record 'COMMON_NAME)))
      (set_tile "summary" (strcat "Code: " (TT:PlantUIString (TT:DataValue record 'PLANT_CODE))
        " | Category: " (TT:PlantCategoryName (TT:DataValue record 'CATEGORY))
        " | Family: " (TT:PlantUIString (TT:DataValue record 'FAMILY))))
      (setq id (if (= mode 0) (TT:DataValue record 'MASTER_PLANT_ID) (TT:DataValue record 'PLANT_ID)))
      (if (= mode 0)
        (progn
          (setq source (TT:PlantProjectSourceStatus record))
          (set_tile "source" (if (= source "SOURCE AVAILABLE") "Original library source available. This is your editable project copy."
            "Original library source unavailable. Your project copy is still usable."))
          (set_tile "description" (strcat "Size: " (TT:PlantUIString (TT:DataValue record 'SIZE))
            " | Spacing: " (TT:PlantUIString (TT:DataValue record 'SPACING))
            " | Unit cost: " (TT:PlantUIString (TT:DataValue record 'UNIT_COST)))))
        (progn
          (setq source (cond ((member id sample-ids) "Built-in Sample Library | Fictional demonstration plant")
            ((wcmatch id "WFO-*") "World Flora Online | Taxonomy only; review design suitability")
            (T (strcat "Plant Library | " (TT:PlantUIString (TT:DataValue record 'SOURCE))))))
          (set_tile "source" source)
          (setq added (TT:DataFindByValue project-plants 'MASTER_PLANT_ID id))
          (set_tile "description" (if added "Already used in this project. Add with a different code for another variant."
            "Add to Project creates an editable copy for your design."))))
      (set_tile "favorite" (if (member id (TT:ProjectValue project 'PLANT_FAVORITES)) "Unfavorite" "Favorite")))
    (foreach source '("name" "common" "summary" "source" "description") (set_tile source ""))))

(defun TT:PlantUIPage (/ record key index)
  (setq visible (TT:PlantPage results page 30) index 0)
  (start_list "plants") (foreach record visible (add_list (TT:PlantUIRow record))) (end_list)
  (foreach record visible
    (if (equal selected-key (TT:PlantUIKey record)) (set_tile "plants" (itoa index)))
    (setq index (1+ index)))
  (if (not (member selected-key (mapcar 'TT:PlantUIKey visible))) (set_tile "plants" "0"))
  (set_tile "page" (strcat "Page " (itoa (1+ page)) " of " (itoa (max 1 (fix (/ (+ (length results) 29) 30))))
    " | " (itoa (length results)) " displayed matches"))
  (mode_tile "previous" (if (> page 0) 0 1))
  (mode_tile "next" (if (< (* (1+ page) 30) (length results)) 0 1))
  (foreach key '("variant" "edit" "remove" "place" "add" "favorite" "details" "area")
    (mode_tile key (if (TT:PlantUIActionEnabledP key project visible mode) 0 1)))
  (TT:PlantUIDetails))

(defun TT:PlantUIRefresh (/ query category index all item ids id)
  (setq query (get_tile "query") mode (atoi (get_tile "mode"))
        index (atoi (get_tile "category")) category (if (> index 0) (nth (1- index) *TT:PlantCategories*))
        page (if preserve-page page 0) project (TT:ProjectCurrent)
        project-plants (if project (TT:PlantPaletteGetAllFromPalette (TT:PlantPaletteLoadFromProject project))))
  (if (= mode 0)
    (progn
      (setq all project-plants results nil)
      (foreach item all
        (if (TT:PlantSearchMatchesP (cons item (TT:PlantSearchText item))
              (TT:StringWords (strcase query)) category nil nil) (setq results (cons item results))))
      (setq results (reverse results)))
    (if (member mode '(2 3))
      (progn
        (setq ids (if project (TT:ProjectValue project (if (= mode 2) 'PLANT_FAVORITES 'PLANT_RECENT))) results nil)
        (foreach id ids
          (if (setq item (TT:PlantMasterFindByID id))
            (if (TT:PlantSearchMatchesP (cons item (TT:PlantSearchText item))
                  (TT:StringWords (strcase query)) category nil nil) (setq results (cons item results)))))
        (setq results (reverse results)))
      (progn
        (set_tile "status" "Searching local plant libraries...")
        (setq results (TT:PlantSearch query category nil))
        (if (or (null category) (eq category 'OTHER))
          (setq results (append results (TT:PlantDatabaseSearch query)))))))
  (setq page (min page (max 0 (1- (fix (/ (+ (length results) 29) 30))))))
  (set_tile "scope"
    (cond ((= mode 0) (strcat (itoa (length project-plants)) " Project Plants | " (itoa (length results)) " match this search. Library plants are separate."))
      ((= mode 2) "Favorites | Saved library plants for this project; unavailable sources are omitted.")
      ((= mode 3) "Recent | Recently added library plants; unavailable sources are omitted.")
      (T "Plant Library | Search sources, then Add to Project to use a plant in your design.")))
  (set_tile "status" (if feedback feedback
    (cond
      ((and (= mode 1) manifest category (not (eq category 'OTHER))) "WFO has no design categories. Choose All categories to include the open database.")
      ((and (= mode 1) manifest (< (strlen (vl-string-trim " " query)) 2)) "Only sample/user plants shown. Enter at least two letters to search the open database.")
      ((and (= mode 1) manifest (= (getvar "LISPSYS") 0)) "Open database search needs LISPSYS 1 or 2 and an LT restart. Samples remain available.")
      ((null project) "Browse freely. Create or open a project from Home to add, favorite or place plants.")
      ((and (= mode 0) (null project-plants)) "No Project Plants yet. Choose Search Plant Library, then Add to Project.")
      ((>= (length results) 500) "Broad search: results are limited. Add more of the plant name to narrow them.")
      ((and (= mode 2) (null results)) "No matching Favorites. Search Plant Library and use Favorite; unavailable sources are omitted.")
      ((and (= mode 3) (null results)) "No matching Recent plants. Add a library plant to this project to begin.")
      ((null results) "No matching plants. Clear the search or choose All categories; check the selected view.")
      ((= mode 0) "Showing project-owned plants. Search Plant Library to add more.")
      (T "Select a plant to review it. Add to Project keeps the library record unchanged."))))
  (TT:PlantUIPage))

(defun TT:PlantUIEditAccept (/ value cost pair code plants)
  (setq value (get_tile "cost") cost (if (= value "") "" (TT:StrictDecimal value)))
  (setq code (vl-string-trim " " (get_tile "code"))
    plants (TT:PlantPaletteGetAllFromPalette (TT:PlantPaletteLoad)))
  (cond
    ((TT:PlantPaletteCodeExistsP plants code (TT:DataValue edit-record 'PROJECT_PLANT_ID))
      (set_tile "error" (strcat "Code '" code "' is already used. Choose a unique code for this plant.")))
    ((= (vl-string-trim " " (get_tile "code")) "") (set_tile "error" "Enter a project plant code."))
    ((or (null cost) (and (numberp cost) (< cost 0.0))) (set_tile "error" "Unit cost must be nonnegative or blank."))
    (T
      (setq edited (TT:DataPut edit-record 'PLANT_CODE (vl-string-trim " " (get_tile "code"))))
      (foreach pair '(("size" . SIZE) ("spacing" . SPACING) ("symbol" . SYMBOL_BLOCK) ("notes" . NOTES))
        (setq edited (TT:DataPut edited (cdr pair) (get_tile (car pair)))))
      (setq edited (TT:DataPut edited 'UNIT_COST cost)
            edited (TT:DataPut edited 'CATEGORY (nth (atoi (get_tile "category")) *TT:PlantCategories*)))
      (if (TT:PlantPaletteRecordValidate edited) (done_dialog 1)
        (set_tile "error" (TT:PlantLastError))))))

(defun TT:PlantUIEditRecord (edit-record / dialog-id edited index pair category)
  (setq dialog-id (load_dialog (TT:StorageJoinPath *TT:Root* "dialogs/terratools-plants.dcl")))
  (if (and (> dialog-id 0) (new_dialog "terratools_plant_edit" dialog-id))
    (progn
      (set_tile "plant_name" (TT:DataValue edit-record 'BOTANICAL_NAME))
      (foreach pair '(("code" . PLANT_CODE) ("size" . SIZE) ("spacing" . SPACING)
                      ("cost" . UNIT_COST) ("symbol" . SYMBOL_BLOCK) ("notes" . NOTES))
        (set_tile (car pair) (TT:PlantUIString (TT:DataValue edit-record (cdr pair)))))
      (start_list "category") (foreach category *TT:PlantCategories* (add_list (TT:PlantCategoryName category))) (end_list)
      (setq index (vl-position (TT:DataValue edit-record 'CATEGORY) *TT:PlantCategories*))
      (set_tile "category" (itoa (if index index 9)))
      (action_tile "accept" "(TT:PlantUIEditAccept)")
      (action_tile "cancel" "(setq edited nil)(done_dialog 0)")
      (start_dialog))
    (princ "\nPlant editor could not be opened. Reload TerraTools and check its trusted dialogs folder."))
  (if (> dialog-id 0) (unload_dialog dialog-id))
  edited)

(defun TT:PlantPaletteCodeExistsP (plants code except-id / found plant)
  (foreach plant plants
    (if (and (equal (strcase code) (strcase (TT:DataValue plant 'PLANT_CODE)))
             (not (equal except-id (TT:DataValue plant 'PROJECT_PLANT_ID)))) (setq found T)))
  found)

(defun TT:PlantPaletteStoreRecord (record old / palette plants)
  (setq palette (TT:PlantPaletteLoad) plants (TT:PlantPaletteGetAllFromPalette palette))
  (cond ((null palette) nil)
    ((TT:PlantPaletteCodeExistsP plants (TT:DataValue record 'PLANT_CODE) (TT:DataValue record 'PROJECT_PLANT_ID))
      (princ (strcat "\nPlant code '" (TT:DataValue record 'PLANT_CODE) "' is already used. Choose a unique project code.")) nil)
    (T (TT:PlantPaletteSave (TT:PlantPaletteWithPlants palette
         (if old (subst record old plants) (append plants (list record))))))))

(defun TT:PlantRecordReferencedP (id project / found item mix component)
  (foreach item (TT:SmartScan)
    (if (equal id (cdr (assoc 'CATALOG_ID (cdr item)))) (setq found T)))
  (foreach mix (TT:ProjectValue project 'PLANT_MIXES)
    (foreach component (TT:DataValue mix 'COMPONENTS)
      (if (equal id (TT:DataValue component 'PROJECT_PLANT_ID)) (setq found T))))
  found)

(defun TT:PlantUIAction (action selected / *error* undo-open record old project point palette answer message count id was-favorite)
  (defun *error* (error-message)
    (if undo-open (command-s "_.UNDO" "_End"))
    (TT:ReportError "Plants" error-message))
  (setq project (TT:ProjectCurrent) message "No changes made.")
  (cond
    ((= action 8) (TT:UXMenu 'PLANTS) (setq message "Planting tools closed. Your search and view are retained."))
    ((= action 9) (C:TTACTIVEWORKAREA) (setq message (TT:UXAreaContext (TT:ProjectCurrent))))
    ((not (setq record (TT:PlantResolveSummary selected)))
      (setq message "This library plant is unavailable. Reattach its library or choose another plant."))
    ((= action 7) (TT:UIRecordDetails record) (setq message "Details closed. Project data is unchanged."))
    ((null project) (setq message "Open a project from Home before adding or editing Project Plants."))
    ((= action 5)
      (setq id (if (TT:DataValue record 'PROJECT_PLANT_ID) (TT:DataValue record 'MASTER_PLANT_ID) (TT:DataValue record 'PLANT_ID))
        was-favorite (member id (TT:ProjectValue project 'PLANT_FAVORITES)))
      (if (TT:PlantToggleFavorite (TT:DataPut record 'PLANT_ID id))
        (setq message (strcat (TT:DataValue record 'BOTANICAL_NAME) (if was-favorite " removed from Favorites." " added to Favorites.")))
        (setq message "Favorites could not be saved. Check project access and try again.")))
    ((member action '(1 2 3))
      (setq old (if (= action 3) record))
      (if (not (TT:DataValue record 'PROJECT_PLANT_ID)) (setq record (TT:PlantProjectRecordFromMaster record)))
      (if (= action 2) (setq record (TT:DataPut record 'PROJECT_PLANT_ID (TT:GenerateUUID))
                            record (TT:DataPut record 'PLANT_CODE (strcat (TT:DataValue record 'PLANT_CODE) "-V"))))
      (if (setq record (TT:PlantUIEditRecord record))
        (if (TT:PlantPaletteStoreRecord record old)
          (progn
            (TT:PlantRememberRecent (TT:DataValue record 'MASTER_PLANT_ID))
            (setq message (strcat (TT:DataValue record 'BOTANICAL_NAME)
              (if old " updated as " " added to Project Plants as ") (TT:DataValue record 'PLANT_CODE) ".")))
          (setq message (strcat "Plant was not saved. " (TT:PlantUIString (TT:PlantLastError)))))))
    ((= action 4)
      (if (TT:PlantRecordReferencedP (TT:DataValue record 'PROJECT_PLANT_ID) project)
        (setq message "Plant is in use. Replace its drawing or mix uses before removing it; check other DWGs too.")
        (progn
          (initget "Yes No")
          (setq answer (getkword (strcat "\nRemove " (TT:DataValue record 'PLANT_CODE) " | " (TT:DataValue record 'BOTANICAL_NAME)
            " from Project Plants? Check other DWGs first. [Yes/No] <No>: ")))
          (if (= answer "Yes")
            (progn (setq palette (TT:PlantPaletteLoad))
              (if (TT:PlantPaletteSave (TT:PlantPaletteWithPlants palette (vl-remove record (TT:PlantPaletteGetAllFromPalette palette))))
                (setq message (strcat (TT:DataValue record 'PLANT_CODE) " removed from Project Plants. Library plant kept."))
                (setq message "Plant was not removed. Check project write access.")))))))
    ((= action 6)
      (if (TT:DataValue record 'PROJECT_PLANT_ID)
        (progn
          (setq count 0) (command-s "_.UNDO" "_Begin") (setq undo-open T)
          (while (setq point (getpoint "\nPlant point <finish>: "))
            (if (TT:PlantCreateInstance project record (trans point 1 0) nil) (setq count (1+ count))))
          (command-s "_.UNDO" "_End") (setq undo-open nil)
          (setq message (strcat (itoa count) " " (TT:DataValue record 'PLANT_CODE) " plants placed. Undo reverses this placement.")))
        (setq message "Add this library plant to Project Plants before placing it."))))
  (princ (strcat "\n" message)) message)

(defun TT:PlantManager (initial-mode / *error* dialog-id mode project project-plants results visible page record pair selected action done category saved-query saved-category selected-key preserve-page feedback manifest sample-ids)
  (defun *error* (message)
    (if (and dialog-id (> dialog-id 0)) (unload_dialog dialog-id))
    (TT:ReportError "Plants" message))
  (setq mode initial-mode action 1 page 0 saved-query "" saved-category "0"
    sample-ids (mapcar '(lambda (r) (TT:DataValue r 'PLANT_ID))
      (TT:PlantMasterCatalogValue (TT:PlantMasterLoad) 'PLANTS)))
  (while (> action 0)
    (setq dialog-id (load_dialog (TT:StorageJoinPath *TT:Root* "dialogs/terratools-plants.dcl")))
    (if (and (> dialog-id 0) (new_dialog "terratools_plants" dialog-id))
      (progn
        (setq project (TT:ProjectCurrent) manifest (TT:PlantDatabaseManifest))
        (set_tile "context" (TT:UXProjectContext project))
        (set_tile "workarea" (TT:UXAreaContext project))
        (set_tile "database" (TT:UXDatabaseBanner manifest))
        (set_tile "samples" (strcat "Built-in Sample Library: " (itoa (length sample-ids))
          " fictional demonstration plants. " (if manifest "Separate from the open database." "See Tools > Plant libraries for installation.")))
        (start_list "mode") (mapcar 'add_list '("Project Plants" "Search Plant Library" "Favorites" "Recent")) (end_list)
        (set_tile "mode" (itoa mode)) (set_tile "query" saved-query)
        (start_list "category") (add_list "All categories")
        (foreach category *TT:PlantCategories* (add_list (TT:PlantCategoryName category))) (end_list)
        (set_tile "category" saved-category)
        (action_tile "search" "(setq feedback nil preserve-page nil)(TT:PlantUIRefresh)")
        (action_tile "mode" "(setq feedback nil preserve-page nil selected-key nil)(TT:PlantUIRefresh)")
        (action_tile "category" "(setq feedback nil preserve-page nil)(TT:PlantUIRefresh)")
        (action_tile "browse" "(set_tile \"mode\" \"1\")(set_tile \"category\" \"0\")(setq feedback nil preserve-page nil)(TT:PlantUIRefresh)(mode_tile \"query\" 2)")
        (action_tile "projectview" "(set_tile \"mode\" \"0\")(setq feedback nil preserve-page nil)(TT:PlantUIRefresh)")
        (action_tile "plants" "(setq selected-key (TT:PlantUIKey (TT:PlantUISelected)))(TT:PlantUIDetails)")
        (action_tile "previous" "(setq page (1- page) selected-key nil)(TT:PlantUIPage)")
        (action_tile "next" "(setq page (1+ page) selected-key nil)(TT:PlantUIPage)")
        (foreach pair '(("add" . 1) ("variant" . 2) ("edit" . 3) ("remove" . 4)
                        ("favorite" . 5) ("place" . 6) ("details" . 7) ("tools" . 8) ("area" . 9))
          (action_tile (car pair) (strcat "(setq selected (TT:PlantUISelected) selected-key (TT:PlantUIKey selected) saved-query (get_tile \"query\") saved-category (get_tile \"category\"))(done_dialog " (itoa (cdr pair)) ")")))
        (action_tile "cancel" "(done_dialog 0)")
        (setq preserve-page T) (TT:PlantUIRefresh)
        (setq action (start_dialog)) (unload_dialog dialog-id) (setq dialog-id nil done T)
        (if (> action 0) (setq feedback (TT:PlantUIAction action selected))))
      (progn (if (> dialog-id 0) (unload_dialog dialog-id)) (setq dialog-id nil action 0))))
  done)

(defun C:TTPLANTS () (if (not (TT:PlantManager 0)) (C:TTPLANTSCLI)) (princ))
(defun C:TTPLANTSEARCH () (if (not (TT:PlantManager 1)) (C:TTPLANTSEARCHCLI)) (princ))
T

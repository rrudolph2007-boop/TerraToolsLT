;;; DEVELOPMENT ONLY. Run in a disposable drawing/profile. Writes a unique TEMP project.
(defun TT:RegressionAssert (condition name)
  (princ (strcat "\nREGRESSION " (if condition "PASS " "FAIL ") name))
  (if (not condition) (setq regression-failures (1+ regression-failures)))
  condition)

(defun TT:RegressionEdge (id start end)
  (list 'NETWORK_EDGE (cons 'EDGE_ID id) (cons 'START start) (cons 'END end)
    '(LENGTH_FT . 100.0) '(DATA (DIAMETER_IN . 1.0) (C_FACTOR . 150.0))))

(defun TT:RunRegression (/ regression-failures graph edges demands pressure record second palette project directory path time0 result entity p failed-file dcl-id)
  (setq regression-failures 0)
  (TT:RegressionAssert (equal (TT:ParseDimension "5' 6\"") '(5.5 FEET)) "feet/inches parser")
  (TT:RegressionAssert (null (TT:ParseDimension "1.2.3 ft")) "reject malformed number")
  (TT:RegressionAssert (null (TT:ParseDimension "+ ft")) "reject sign without digits")
  (TT:RegressionAssert (and (TT:StorageDataTextP "(A (B . 1))")
    (not (TT:StorageDataTextP "(A) (B)")) (not (TT:StorageDataTextP "(A)) ignored"))) "single storage expression")
  (TT:RegressionAssert (TT:PointInPolygon '(5 5) '((0 0) (10 0) (10 10) (0 10))) "polygon inside")
  (TT:RegressionAssert (not (TT:PointInPolygon '(15 5) '((0 0) (10 0) (10 10) (0 10)))) "polygon outside")
  (TT:RegressionAssert (= (TT:BulgeSegmentSignedArea '(0 0) '(0 0) 1.0) 0.0) "degenerate bulge")
  (setq entity (entmakex '((0 . "LINE") (10 0.0 0.0 1.0) (11 10.0 0.0 11.0))))
  (TT:RegressionAssert (equal (TT:EntityPointAtDistance entity (/ (TT:EntityLength entity) 2.0)) '(5.0 0.0 6.0) 1e-8) "3D line midpoint")
  (entdel entity)
  (setq edges (list (TT:RegressionEdge 0 '(0.0 0.0 0.0) '(10.0 0.0 0.0))
    (TT:RegressionEdge 1 '(10.0 0.0 0.0) '(20.0 10.0 0.0))
    (TT:RegressionEdge 2 '(10.0 0.0 0.0) '(20.0 -10.0 0.0)))
    demands '(((20.0 10.0 0.0) 2.0 30.0 0.0) ((20.0 -10.0 0.0) 3.0 40.0 0.0))
    graph (TT:NetworkBuild edges demands '((0.0 0.0 0.0)) 0.01))
  (TT:RegressionAssert (null (TT:DataValue graph 'ERRORS)) "branched network topology")
  (TT:RegressionAssert (= (cdr (assoc (TT:DataValue graph 'ROOT) (TT:DataValue graph 'FLOWS))) 5.0) "downstream root flow")
  (setq pressure (TT:NetworkPressure graph 60.0 'FEET))
  (TT:RegressionAssert (and pressure (> (TT:DataValue pressure 'SOURCE_REQUIRED_PSI) 40.0)
    (= (length (TT:DataValue pressure 'CRITICAL_EDGE_IDS)) 2)) "automatic critical path")
  (setq graph (TT:NetworkBuild (append edges (list (TT:RegressionEdge 3 '(20.0 10.0 0.0) '(10.0 0.0 0.0)))) demands '((0.0 0.0 0.0)) 0.01))
  (TT:RegressionAssert (and (TT:DataValue graph 'ERRORS) (null (TT:NetworkPressure graph 60.0 'FEET))) "refuse loop/merge pressure")
  (setq directory (TT:StorageJoinPath (getenv "TEMP") (strcat "TTRegression-" (TT:GenerateUUID))))
  (vl-mkdir directory)
  (setq project (TT:ProjectCreate directory "QA" "Regression" "" "" "Disposable regression project" "Feet") path *TT:CurrentProjectPath*)
  (TT:RegressionAssert project "project create")
  (setq record (TT:PlantProjectRecordFromMaster (car (TT:PlantMasterGetAll)))
        record (TT:DataPut record 'MASTER_PLANT_ID "SOURCE-UNAVAILABLE-TEST")
        second (TT:DataPut record 'PROJECT_PLANT_ID (TT:GenerateUUID))
        second (TT:DataPut second 'PLANT_CODE "QA-VARIANT")
        palette (TT:PlantPaletteWithPlants (TT:PlantPaletteEmpty) (list record second)))
  (TT:RegressionAssert (TT:PlantPaletteValidate palette) "source-independent variants")
  (TT:RegressionAssert (TT:PlantPaletteSave palette) "save variants")
  (TT:RegressionAssert (= (length (TT:PlantPaletteGetAllFromPalette (TT:PlantPaletteLoad))) 2) "reopen palette")
  (TT:RegressionAssert (= (TT:PlantProjectSourceStatus record) "SOURCE UNAVAILABLE") "source diagnostic")
  (TT:ProjectClose)
  (TT:RegressionAssert (and (TT:StorageFileExistsP path) (null (TT:ProjectCurrent))) "close preserves project")
  (TT:RegressionAssert (TT:ProjectOpen path) "project reopen")
  (setq failed-file (strcat path ".moved")) (vl-file-rename path failed-file)
  (TT:RegressionAssert (and (null (TT:ProjectCurrent)) (TT:ProjectGetAssociation)) "missing file retains unresolved association")
  (vl-file-rename failed-file path)
  (TT:RegressionAssert (TT:ProjectCurrent) "restored path")
  (TT:RegressionAssert (TT:ProjectSave (TT:ProjectCurrent) path) "backup write")
  (TT:RegressionAssert (TT:ProjectRecover path (TT:ProjectValue project 'PROJECT_UUID)) "deliberate backup recovery")
  (setq time0 (getvar "MILLISECS") result (TT:PlantDatabaseSearch "Acer rubrum"))
  (princ (strcat "\nBENCHMARK WFO search milliseconds: " (itoa (- (getvar "MILLISECS") time0))))
  (TT:RegressionAssert (> (length result) 0) "real WFO name search")
  (setq record (if result (TT:PlantResolveSummary (car result))))
  (TT:RegressionAssert (and record (TT:PlantMasterRecordValidate record)) "lazy WFO record lookup")
  (TT:RegressionAssert (= (TT:DataValue record 'DESCRIPTION_COMPLETENESS) "TAXONOMY_ONLY") "description provenance")
  (TT:RegressionAssert (TT:PlantPaletteAddMaster record) "WFO project snapshot")
  (setq dcl-id (vl-catch-all-apply 'load_dialog (list (TT:StorageJoinPath *TT:Root* "dialogs/terratools-plants.dcl"))))
  (princ (strcat "\nDCL DIAGNOSTIC: " (if (vl-catch-all-error-p dcl-id)
    (vl-catch-all-error-message dcl-id) (vl-princ-to-string dcl-id))))
  (if (and (not (vl-catch-all-error-p dcl-id)) (> dcl-id 0))
    (TT:RegressionAssert T "DCL resource loads")
    (princ "\nREGRESSION SKIP DCL: Core Console also returns -1 for a minimal standalone dialog. GUI acceptance required."))
  (if (and (numberp dcl-id) (> dcl-id 0)) (unload_dialog dcl-id))
  (princ (strcat "\nREGRESSION TOTAL FAILURES: " (itoa regression-failures)))
  (princ (strcat "\nREGRESSION ARTIFACTS: " directory))
  (princ))

(TT:RunRegression)

;;; DEVELOPMENT ONLY: run after lt-regression.lsp in its disposable project.
(defun TT:CompletionRegression (/ regression-failures project copy classes report rows style path package record station controller a b data palette duplicate)
  (setq regression-failures 0 project (TT:ProjectCurrent))
  (TT:RegressionAssert (equal (TT:ProjectMigrate project 1) project) "migration preserves current schema and unknown fields")
  (TT:RegressionAssert (TT:QAApprox (TT:DripAreaDemand 100.0 2.0 1.0 0.5) (/ 25.0 60.0) 1e-8) "drip emitter spacing")
  (setq classes '(PIPE_CLASS (SIZES_TEXT . "1:1.049 1.25:1.380") (C_FACTOR . 150.0)))
  (TT:RegressionAssert (equal (TT:PipeClassSizes classes) '((1.0 1.049) (1.25 1.38)) 1e-8) "actual inside-diameter pairs")
  (TT:RegressionAssert (null (TT:PipeClassSizes '(PIPE_CLASS (SIZES_TEXT . "1:bad")))) "reject malformed class")
  (setq rows '((SCHEDULE_ROW (CODE . "B") (QUANTITY . 2) (CATEGORY . TREE))
               (SCHEDULE_ROW (CODE . "A") (QUANTITY . 2) (CATEGORY . TREE))) style (TT:DefaultScheduleStyle))
  (TT:RegressionAssert (= (length (TT:ScheduleRowsSorted rows style)) 2) "schedule sorting preserves equal-valued rows")
  (TT:RegressionAssert (= (TT:DataValue (car (TT:ScheduleRowsSorted rows style)) 'CODE) "A") "schedule sorts by code")
  (TT:RegressionAssert (equal (TT:CSVParseLine "\"two\nlines\",\"ok\"") '("two\nlines" "ok")) "CSV quoted newline")
  (TT:RegressionAssert (null (TT:CSVParseLine "ab\"c,def")) "CSV rejects quotes in unquoted field")
  (TT:RegressionAssert (and (TT:PackageRelativePathP "resources/a.dwg")
    (not (TT:PackageRelativePathP "../outside.dwg")) (not (TT:PackageRelativePathP "C:/outside.dwg"))) "package traversal rejection")
  (setq controller '(IRRIGATION_CONTROLLERS (CONTROLLER_ID . "QA-C") (NAME . "QA Controller") (CAPACITY . 2) (DESCRIPTION . "Test")))
  (TT:RegressionAssert (TT:ManagerSaveRecord 'CONTROLLER controller nil) "controller persistence")
  (setq station '(IRRIGATION_STATIONS (STATION_ID . "QA-S") (NAME . "QA Station") (CONTROLLER . "QA Controller") (OUTPUT . 1) (NOTES . "Test")))
  (TT:RegressionAssert (TT:ManagerSaveRecord 'STATION station nil) "station assignment persistence")
  (TT:RegressionAssert (not (TT:ManagerSaveRecord 'STATION (TT:DataPut (TT:DataPut station 'STATION_ID "QA-S2") 'NAME "Second") nil)) "duplicate controller output rejected")
  (setq package (TT:StorageJoinPath (getenv "TEMP") (strcat "TTPackageQA-" (TT:GenerateUUID))))
  (TT:RegressionAssert (TT:PackageCreate package nil) "project package creation")
  (TT:RegressionAssert (TT:PackageOpen (TT:StorageJoinPath package "terratools-package.dat")) "package reopen")
  (TT:RegressionAssert (equal (TT:ProjectValue (TT:ProjectCurrent) 'PROJECT_UUID) (TT:ProjectValue project 'PROJECT_UUID)) "package project identity retained")
  (setq palette (TT:PlantPaletteLoad) record (car (TT:PlantPaletteGetAllFromPalette palette))
    duplicate (TT:DataPut record 'PROJECT_PLANT_ID (TT:GenerateUUID)))
  (TT:RegressionAssert (not (TT:PlantPaletteSave (TT:PlantPaletteWithPlants palette
    (append (TT:PlantPaletteGetAllFromPalette palette) (list duplicate))))) "central duplicate code save guard")
  (setq a (entmakex '((0 . "POINT") (10 0.0 0.0 0.0))) b (entmakex '((0 . "POINT") (10 1.0 0.0 0.0)))
    data (TT:SmartMetadata project "CORE" "WORK_AREA" "TEST-AREA" nil))
  (TT:SetEntityXData a data) (TT:SetEntityXData b data)
  (TT:RegressionAssert (= (cdr (assoc 'DUPLICATES (TT:ReconcileScan nil))) 1) "sorted scan retains duplicate UUID entities")
  (TT:RegressionAssert (= (cdr (assoc 'REPAIRED (TT:ReconcileScan T))) 1) "sorted duplicate repair")
  (TT:RegressionAssert (not (TT:ManagerIdentityInUse '(WORK_AREA (WORK_AREA_ID . "TEST-AREA"))
    (TT:ManagerConfig 'WORK) (list (cons a data)))) "work area own boundary is not a dependency")
  (setq data (append (TT:GetEntityXData a) '((COVERAGE_RADIUS . 10.0) (COVERAGE_SWEEP . 90.0) (PRESSURE_PSI . 30.0))))
  (TT:SetEntityXData a data)
  (TT:RegressionAssert (and (= (cdr (assoc 'COVERAGE_SWEEP (TT:GetEntityXData a))) 90.0)
    (= (cdr (assoc 'PRESSURE_PSI (TT:GetEntityXData a))) 30.0)) "coverage sweep and drip pressure XData round trip")
  (entdel a) (entdel b)
  (setq record (TT:LibraryNormalize (car (TT:DataValue (TT:IrrigationMasterLoad) 'EQUIPMENT)) 'IRR))
  (TT:RegressionAssert (TT:LibraryValidate (list 'TT_USER_LIBRARY '(SCHEMA_VERSION . 1) '(KIND . IRR) (cons 'RECORDS (list record))) 'IRR) "sample irrigation library normalization")
  (TT:RegressionAssert (TT:DataValue (car (TT:PipeClasses)) 'CLASS_ID) "legacy pipe class identity resolves")
  (TT:RegressionAssert (not (TT:PackageRelativePathP "resources/../escape.dat")) "nested traversal rejected")
  (princ (strcat "\nCOMPLETION REGRESSION FAILURES: " (itoa regression-failures)))
  (princ))
(TT:CompletionRegression)

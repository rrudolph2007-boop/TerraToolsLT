;;; DEVELOPMENT ONLY: read-only UI logic checks. No DCL rendering claim.
(defun TT:UXRegression (/ failures check checks manifest kind tasks task missing names sample-ids record manager-visible)
  (setq failures 0 manifest (TT:PlantDatabaseManifest)
    checks (list
      (cons "manager nil records" (null (TT:ManagerSelection nil "0")))
      (cons "manager empty search result" (null (TT:ManagerSelection (vl-remove 'FIRST '(FIRST)) "0")))
      (cons "manager valid first record" (equal (TT:ManagerSelection '(FIRST SECOND) "0") 'FIRST))
      (cons "manager valid last record" (equal (TT:ManagerSelection '(FIRST SECOND) "1") 'SECOND))
      (cons "manager missing selection" (null (TT:ManagerSelection '(FIRST) nil)))
      (cons "manager blank selection" (null (TT:ManagerSelection '(FIRST) "")))
      (cons "manager nonnumeric selection" (null (TT:ManagerSelection '(FIRST) "bad")))
      (cons "manager mixed selection" (null (TT:ManagerSelection '(FIRST) "0bad")))
      (cons "manager negative selection" (null (TT:ManagerSelection '(FIRST) "-1")))
      (cons "manager fractional selection" (null (TT:ManagerSelection '(FIRST) "0.5")))
      (cons "manager multiple indices" (null (TT:ManagerSelection '(FIRST SECOND) "0 1")))
      (cons "manager out-of-range selection" (null (TT:ManagerSelection '(FIRST SECOND) "2")))
      (cons "manager overflowing selection" (null (TT:ManagerSelection '(FIRST) "4294967296")))
      (cons "manager oversized selection" (null (TT:ManagerSelection '(FIRST) "999999999999999999999")))
      (cons "manager numeric non-string selection" (null (TT:ManagerSelection '(FIRST) 0)))
      (cons "empty manager needs no DCL selection" (null (TT:ManagerSelected)))
      (cons "Work Area empty state preserved" (= (TT:ManagerEmptyText 'WORK)
        "No Work Areas yet. Add a closed boundary to organize objects and schedules."))
      (cons "count grouping" (and (= (TT:UXCount 15) "15") (= (TT:UXCount 435702) "435,702") (= (TT:UXCount 1000000) "1,000,000")))
      (cons "missing database explains samples" (vl-string-search "samples" (TT:UXDatabaseBanner nil)))
      (cons "banner uses supplied count" (vl-string-search "123,456" (TT:UXDatabaseBanner '(TT_PLANT_DATABASE (ACCEPTED_COUNT . 123456) (DATABASE_VERSION . "TEST")))))
      (cons "library cannot place" (not (TT:PlantUIActionEnabledP "place" T T 1)))
      (cons "project can place" (TT:PlantUIActionEnabledP "place" T T 0))
      (cons "empty project cannot edit" (not (TT:PlantUIActionEnabledP "edit" T nil 0)))
      (cons "no project cannot add" (not (TT:PlantUIActionEnabledP "add" nil T 1)))
      (cons "library can add to project" (TT:PlantUIActionEnabledP "add" T T 1))
      (cons "project cannot add as source" (not (TT:PlantUIActionEnabledP "add" T T 0)))
      (cons "no project can inspect source" (TT:PlantUIActionEnabledP "details" nil T 1))
      (cons "variant only in project view" (and (TT:PlantUIActionEnabledP "variant" T T 0) (not (TT:PlantUIActionEnabledP "variant" T T 1))))
      (cons "no project guidance" (vl-string-search "Create or open" (TT:UXProjectContext nil)))))
  (foreach kind '(WORK SITE DETAIL LIGHT IRR STATION CONTROLLER)
    (setq checks (cons (cons (strcat "empty state " (vl-symbol-name kind))
      (and (> (strlen (TT:ManagerEmptyText kind)) 20) (> (strlen (TT:ManagerGuidance kind)) 20))) checks)))
  (setq names (atoms-family 1))
  (foreach kind '(PROJECT PLANTS DATA WORK SITE DETAIL LIGHT IRR STATION CONTROLLER OUTPUT CHECK RECOVERY)
    (setq tasks (TT:UXTasks kind))
    (if (null tasks) (setq missing T))
    (foreach task tasks (if (not (member (vl-symbol-name (cadr task)) names)) (setq missing T))))
  (setq checks (cons (cons "workflow task symbols present" (not missing)) checks)
    record (car (TT:PlantMasterCatalogValue (TT:PlantMasterLoad) 'PLANTS))
    sample-ids (list (TT:DataValue record 'PLANT_ID))
    checks (cons (cons "sample row visibly marked" (vl-string-search "SAMPLE" (TT:PlantUIRow record))) checks))
  (if manifest (setq checks (cons (cons "installed banner reflects real database" (vl-string-search
    (TT:UXCount (TT:DataValue manifest 'ACCEPTED_COUNT)) (TT:UXDatabaseBanner manifest))) checks)))
  (foreach check (reverse checks)
    (princ (strcat "\nUX CHECK " (if (cdr check) "PASS " "FAIL ") (car check)))
    (if (not (cdr check)) (setq failures (1+ failures))))
  (princ (strcat "\nUX LOGIC FAILURES: " (itoa failures) " | checks: " (itoa (length checks))))
  (princ))
(TT:UXRegression)

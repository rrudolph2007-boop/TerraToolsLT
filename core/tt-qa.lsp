;;; TerraTools LT - Read-only deterministic pure-function checks.

(setq *TT:QAModuleLoaded* T)

(defun TT:QAApprox (actual expected tolerance)
  (and (numberp actual) (<= (abs (- actual expected)) tolerance)))

(defun TT:QALine (condition label expected actual)
  (princ (strcat "\n" (if condition "PASS" "FAIL") "  " label))
  (if (not condition)
    (princ (strcat " - expected " expected "; got " actual)))
  condition)

(defun C:TTQACHECK (/ passed value vertices row result diameter)
  (setq passed T)
  (princ "\nTerraTools deterministic QA checks")
  (if (not (TT:QALine (TT:QAApprox (TT:ConvertLength 12.0 'INCHES 'FEET) 1.0 1e-9)
                            "Units: 12 inches = 1 foot" "1.0" (rtos (TT:ConvertLength 12.0 'INCHES 'FEET) 2 8)))
    (setq passed nil))
  (if (not (TT:QALine (TT:QAApprox (TT:ConvertLength 1000.0 'MILLIMETERS 'METERS) 1.0 1e-9)
                            "Units: 1000 mm = 1 m" "1.0" (rtos (TT:ConvertLength 1000.0 'MILLIMETERS 'METERS) 2 8)))
    (setq passed nil))
  (if (not (TT:QALine (equal (TT:ParseDimension "18 in") '(18.0 INCHES))
                           "Units: explicit spacing parse" "(18.0 INCHES)"
                           (vl-princ-to-string (TT:ParseDimension "18 in"))))
    (setq passed nil))
  (setq vertices '(((0.0 0.0) 0.0) ((10.0 0.0) 0.0) ((10.0 20.0) 0.0) ((0.0 20.0) 0.0)))
  (if (not (TT:QALine (and (TT:QAApprox (TT:PolylineAreaFromVertices vertices) 200.0 1e-8)
                            (TT:QAApprox (TT:PolylineLengthFromVertices vertices T) 60.0 1e-8))
                           "Geometry: 10 x 20 rectangle" "area 200, perimeter 60"
                           (strcat "area " (rtos (TT:PolylineAreaFromVertices vertices) 2 4))))
    (setq passed nil))
  (setq vertices '(((0.0 0.0) 1.0) ((2.0 0.0) 0.0)))
  (if (not (TT:QALine (and (TT:QAApprox (TT:PolylineAreaFromVertices vertices) (/ pi 2.0) 1e-8)
                            (TT:QAApprox (TT:PolylineLengthFromVertices vertices T) (+ pi 2.0) 1e-8))
                           "Geometry: closed semicircular bulge" "area pi/2, perimeter pi+2"
                           (strcat "area " (rtos (TT:PolylineAreaFromVertices vertices) 2 6))))
    (setq passed nil))
  (setq vertices '(((0.0 0.0) -1.0) ((2.0 0.0) 0.0)))
  (if (not (TT:QALine (and (TT:QAApprox (TT:PolylineAreaFromVertices vertices) (/ pi 2.0) 1e-8)
                            (TT:QAApprox (TT:PolylineLengthFromVertices vertices nil) pi 1e-8))
                           "Geometry: negative open semicircular bulge" "area pi/2, open length pi"
                           (strcat "length " (rtos (TT:PolylineLengthFromVertices vertices nil) 2 6))))
    (setq passed nil))
  (if (not (TT:QALine (= (TT:PlantQuantityFromArea 100.0 2.0 nil) 25)
                           "Plant density: square spacing" "25" (itoa (TT:PlantQuantityFromArea 100.0 2.0 nil))))
    (setq passed nil))
  (if (not (TT:QALine (= (TT:PlantQuantityFromArea 100.0 2.0 T) 29)
                           "Plant density: triangular spacing" "29" (itoa (TT:PlantQuantityFromArea 100.0 2.0 T))))
    (setq passed nil))
  (setq row (TT:CSVParseLine "\"A, B\",\"He said \"\"yes\"\"\",,C"))
  (if (not (TT:QALine (equal row '("A, B" "He said \"yes\"" "" "C"))
                           "CSV parsing: commas, quotes, blank" "four parsed fields" (if row "parsed" "nil")))
    (setq passed nil))
  (if (not (TT:QALine (equal (TT:CSVJoinRow '("A, B" "He said \"yes\"" ""))
                                  "\"A, B\",\"He said \"\"yes\"\"\",\"\"")
                           "CSV writing: commas, quotes, blank" "quoted CSV row"
                           (TT:CSVJoinRow '("A, B" "He said \"yes\"" ""))))
    (setq passed nil))
  (setq value (TT:HazenWilliamsHeadLossFT 100.0 10.0 1.0 150.0))
  (if (not (TT:QALine (TT:QAApprox value 6.9659697702 1e-6)
                           "Hydraulics: Hazen-Williams" "6.965970 ft" (rtos value 2 6)))
    (setq passed nil))
  (setq value (TT:HydraulicVelocityFPS 10.0 1.0))
  (if (not (TT:QALine (TT:QAApprox value 4.085 1e-6)
                           "Hydraulics: velocity" "4.085 ft/s" (rtos value 2 6)))
    (setq passed nil))
  (setq diameter (TT:HydraulicChooseDiameter 100.0 10.0 150.0 '(0.5 0.75 1.0 1.25 1.5) 5.0 5.0))
  (if (not (TT:QALine (equal diameter 1.0)
                           "Hydraulics: pipe sizing" "1.0 in" (if diameter (rtos diameter 2 2) "nil")))
    (setq passed nil))
  (setq value (TT:LightingVoltageDrop 100.0 12.0 50.0 14))
  (if (not (TT:QALine (TT:QAApprox value 2.6155717762 1e-6)
                           "Lighting: copper voltage drop" "2.615572 V" (rtos value 2 6)))
    (setq passed nil))
  (if (not (TT:QAExtended)) (setq passed nil))
  (princ (strcat "\n\nQA check: " (if passed "PASS" "FAIL")))
  (princ))

T

;;; Presentation helpers only. Task entries are trusted code, never imported data.
(defun TT:UXCount (value / digits result)
  (setq digits (itoa (fix value)) result "")
  (while (> (strlen digits) 3)
    (setq result (strcat "," (substr digits (- (strlen digits) 2)) result)
          digits (substr digits 1 (- (strlen digits) 3))))
  (strcat digits result))

(defun TT:UXProjectContext (project)
  (strcat "Project: " (if project (TT:ProjectValue project 'PROJECT_NAME) "None. Create or open a project to begin.")))

(defun TT:UXAreaContext (project / area)
  (setq area (if project (TT:WorkAreaFind project (TT:ActiveWorkArea project))))
  (strcat "New placements: " (if area (TT:DataValue area 'NAME) "No active Work Area")))

(defun TT:UXDatabaseBanner (manifest)
  (if manifest
    (strcat "Open Plant Database: " (TT:UXCount (TT:DataValue manifest 'ACCEPTED_COUNT))
      " plants available | " (TT:DataValue manifest 'DATABASE_VERSION))
    "Open Plant Database unavailable. Built-in samples are still available."))

(defun TT:UXTaskLabel (task) (car task))

(defun TT:UXTasks (kind)
  ;; Label, function, explanation, requires a readable project.
  (cond
    ((eq kind 'PROJECT)
      '(("Create project" TT:ProjectCommandCreate "Choose a folder and enter project details at the command line." nil)
        ("Open project" TT:ProjectCommandOpen "Select an existing project. Your drawing will use that project." nil)
        ("Project information" C:TTPROJECTINFO "Review the current project and any missing-file problem." nil)
        ("Close project" TT:ProjectCommandClose "Disconnect this drawing. The external project file is kept." nil)))
    ((eq kind 'PLANTS)
      '(("Place along a path" C:TTPLANTPATH "Choose a project plant, a path and spacing." T)
        ("Fill a planting boundary" C:TTPLANTFILL "Place plants inside a supported closed boundary." T)
        ("Rectangular array" C:TTPLANTARRAY "Place a project plant in rows and columns." T)
        ("Spacing area" C:TTGROUND "Assign a plant and square or triangular spacing to a boundary." T)
        ("Density area" C:TTDENSITYAREA "Calculate plants from area and density." T)
        ("Plant mixes" C:TTMIX "Create a reusable mix of project plants." T)
        ("Label selected plants" C:TTLABELGROUP "Create a group label from placed plants." T)
        ("Refresh plant labels" C:TTUPDATEPLANTLABELS "Update labels from current plants and counts." T)
        ("Select similar plants" C:TTSELECTSIMILAR "Select instances of the same project plant." T)
        ("Count selected plants" C:TTCOUNTSELECTED "Report the selected plant count." T)
        ("Plant symbols" C:TTPLANTSYMBOLS "Set project symbol scale and repair default symbols." T)
        ("Plant label style" C:TTLABELSTYLE "Choose fields for project plant labels." T)
        ("Schedules and reports" C:TTSCHEDULES "Create or refresh output from current design records." T)
        ("Verify plants" C:TTVERIFYPLANTS "Check project plants and placed references without changing them." T)
        ("Plant libraries and database" TT:UXPlantData "Check installed data, custom plants and attached libraries." nil)))
    ((eq kind 'DATA)
      '(("Search Plant Library" C:TTPLANTSEARCH "Search available plants. Add creates a project-owned copy." nil)
        ("Installed database information" C:TTPLANTDATABASE "Review database availability and installation guidance." nil)
        ("Custom plant library" C:TTPLANTUSER "Manage your own source plants separately from project plants." nil)
        ("Attach / detach a plant library" C:TTPLANTDATA "Project copies remain usable after a library is detached." T)
        ("Import USDA checklist" C:TTIMPORTUSDA "Convert a downloaded USDA CSV to a local plant library." nil)))
    ((eq kind 'WORK)
      '(("Change active Work Area" C:TTACTIVEWORKAREA "Choose the area for new placements. Enter clears it." T)
        ("Assign selected objects" C:TTASSIGNWORKAREA "Explicitly assign current-project objects to a Work Area." T)
        ("Clear selected assignments" C:TTUNASSIGNWORKAREA "Remove area assignments without deleting objects." T)
        ("Count by Work Area" C:TTCOUNTWORKAREA "Report quantities for a chosen Work Area." T)))
    ((eq kind 'SITE)
      '(("Reference Notes manager" C:TTREFNOTES "Add notes, edit project specifications and assign geometry." T)
        ("Place reference callout" C:TTREFNOTELABEL "Choose note geometry and place its code and description." T)
        ("Refresh reference callouts" C:TTUPDATEREFNOTELABELS "Use current project note text." T)
        ("Reference schedule" C:TTREFNOTESCHEDULE "Create quantities and costs, optionally by Work Area." T)
        ("Measure area" C:TTAREA "Read the area of a supported closed boundary." nil)
        ("Measure length" C:TTLENGTH "Read supported straight or curved geometry length." nil)
        ("Measure volume" C:TTVOLUME "Calculate boundary area times entered depth." nil)
        ("Slope" C:TTSLOPE "Calculate slope from two points and elevations." nil)
        ("Bearing and distance" C:TTBEARINGDIST "Report direction and distance between two points." nil)
        ("Concept boundary" C:TTCONCEPT "Name a closed concept boundary." T)))
    ((eq kind 'DETAIL)
      '(("Place callout" C:TTCALLOUT "Place a reference to a project detail." T)
        ("Renumber detail" C:TTDETAILRENUMBER "Choose a distinct number and update its callouts." T)
        ("Detail index" C:TTDETAILINDEX "Create an index of current project details." T)
        ("Inspect placed detail" C:TTDETAILINFO "Review a selected detail instance." T)
        ("Library and verification commands" C:TTDETAILSCLI "Additional detail commands. Source DWG artwork is not inserted." T)))
    ((eq kind 'LIGHT)
      '(("Match fixtures" C:TTMATCHFIXTURE "Apply one project fixture choice to selected fixtures." T)
        ("Count fixtures" C:TTCOUNTLIGHTING "Report current-project fixture counts." T)
        ("Draw lighting wire" C:TTLIGHTWIRE "Create a smart wire line." T)
        ("Place transformer" C:TTTRANSFORMER "Place a transformer and enter capacity." T)
        ("Assign circuit" C:TTCIRCUITASSIGN "Assign a circuit name to a selected object." T)
        ("Circuit information" C:TTCIRCUITINFO "Report fixture count and connected load." T)
        ("Transformer load" C:TTTRANSFORMERLOAD "Compare connected watts with transformer capacity." T)
        ("Voltage drop" C:TTVOLTAGEDROP "Estimate copper two-conductor voltage drop." nil)
        ("Lighting schedule" C:TTLIGHTINGSCHEDULE "Create a current-project or Work Area schedule." T)
        ("Verify lighting" C:TTVERIFYLIGHTING "Report missing links and overloads." T)))
    ((member kind '(IRR STATION CONTROLLER))
      '(("1. Equipment manager" C:TTIRRIGATION "Add project equipment, then place heads and valves." T)
        ("2. Stations" C:TTSTATIONS "Create stations and assign selected irrigation objects." T)
        ("3. Controllers" C:TTCONTROLLERS "Set controller capacity and station output assignments." T)
        ("4. Pipe classes" C:TTPIPECLASSES "Review nominal and actual inside diameters before drawing." T)
        ("5. Draw directed pipes" C:TTPIPE "Draw from source toward demand; choose class and station." T)
        ("6. Verify equipment" C:TTVERIFYIRRIGATION "Report missing references and equipment data problems." T)
        ("7. Analyze network" C:TTIRRIGATIONANALYZE "Check connections and downstream demand before sizing." T)
        ("8. Size pipes" C:TTIRRIGATIONSIZE "Choose scope and criteria. Protected manual sizes are retained." T)
        ("9. Analyze pressure" C:TTAUTOCRITICALPATH "Enter source pressure to review the limiting route." T)
        ("Manual / automatic pipe size" C:TTPIPEAUTO "Explicitly change one pipe's size protection." T)
        ("Reverse pipe direction" C:TTREVERSEPIPE "Reverse selected pipe endpoints deliberately." T)
        ("Coverage" C:TTIRRIGATIONCOVERAGE "Set radius and arc sweep for a selected head." T)
        ("Refresh coverage" C:TTUPDATECOVERAGE "Recreate coverage after moving or rotating heads." T)
        ("Drip area" C:TTDRIPAREA "Enter emitter and row spacing to derive area demand." T)
        ("Metric hydraulic calculator" C:TTHYDRAULICMETRIC "Calculate from metric inputs using the shared hydraulic engine." nil)
        ("Irrigation schedule" C:TTIRRIGATIONSCHEDULE "Create output by station, Work Area or whole project." T)))
    ((eq kind 'OUTPUT)
      '(("Plant schedule" C:TTPLANTSCHEDULE "Create quantities and costs from current plants." T)
        ("Refresh plant schedule" C:TTUPDATEPLANTSCHEDULE "Select an existing plant schedule to update." T)
        ("Plant schedule style" C:TTSCHEDULESTYLE "Choose columns, ordering and grouping." T)
        ("Plant costs" C:TTPLANTCOST "Review project or Work Area costs." T)
        ("Export plant CSV" C:TTEXPORTPLANTCSV "Export current plant quantities and costs." T)
        ("Reference schedule" C:TTREFNOTESCHEDULE "Create current reference-note quantities." T)
        ("Refresh reference schedule" C:TTUPDATEREFNOTES "Select the reference schedule to rebuild." T)
        ("Detail index" C:TTDETAILINDEX "List project details." T)
        ("Lighting schedule" C:TTLIGHTINGSCHEDULE "Summarize project fixtures." T)
        ("Irrigation schedule" C:TTIRRIGATIONSCHEDULE "Summarize equipment and pipes." T)
        ("Refresh equipment schedule" C:TTUPDATEEQUIPMENTSCHEDULE "Retain the selected schedule's station or Work Area scope." T)))
    ((eq kind 'CHECK)
      '(("Verify drawing" C:TTVERIFY "Read-only check of smart objects and project references." nil)
        ("Verify plants" C:TTVERIFYPLANTS "Read-only check of project plant links and symbols." T)
        ("Repair copied-object identities" C:TTRECONCILE "Assign fresh instance identities to duplicate copies." nil)
        ("Installation smoke test" C:TTDEVSMOKE "Read-only module and project checks." nil)
        ("Calculation checks" C:TTQACHECK "Deterministic read-only calculations." nil)
        ("Environment details" C:TTDEBUG "Technical installation, drawing and project diagnostics." nil)
        ("Reload TerraTools" C:TTRELOAD "Reload this installation after source updates." nil)))
    ((eq kind 'RECOVERY)
      '(("Inspect project connection" C:TTPROJECTINFO "Review the stored path before restoring or reopening anything." nil)
        ("Open moved project" TT:ProjectCommandOpen "Choose the intended project explicitly; no automatic search." nil)
        ("Restore project backup" C:TTRECOVERPROJECT "Inspect a valid backup; restore only after explicit confirmation." nil)
        ("Project package" C:TTPACKAGE "Create or open a package; original project data is preserved." nil)))))

(defun TT:UXTaskDetail (/ task available)
  (setq task (nth (atoi (get_tile "tasks")) ux-tasks)
    available (or (not (nth 3 task)) ux-project))
  (set_tile "description" (nth 2 task))
  (set_tile "status" (if available "Continue starts this task. Back makes no changes."
    "Create or open a readable project first: Home > Project."))
  (mode_tile "accept" (if available 0 1)))

(defun TT:UXMenu (kind / *error* ux-tasks ux-project dialog-id choice selected)
  (defun *error* (message)
    (if (and dialog-id (> dialog-id 0)) (unload_dialog dialog-id))
    (TT:ReportError "Tools" message))
  (setq ux-tasks (TT:UXTasks kind) ux-project (TT:ProjectCurrent)
    dialog-id (load_dialog (TT:StorageJoinPath *TT:Root* "dialogs/terratools-main.dcl")))
  (if (and (> dialog-id 0) (new_dialog "terratools_tools" dialog-id))
    (progn
      (set_tile "title" (strcat "TerraTools | " (TT:UXTitle kind)))
      (set_tile "context" (TT:UXProjectContext ux-project))
      (set_tile "guide" (if (member kind '(IRR STATION CONTROLLER))
        "Equipment > Stations > Pipes > Verify > Size > Pressure > Output"
        "Choose a task to see what it does before continuing."))
      (start_list "tasks") (foreach selected ux-tasks (add_list (car selected))) (end_list)
      (set_tile "tasks" "0") (TT:UXTaskDetail)
      (action_tile "tasks" "(TT:UXTaskDetail)")
      (action_tile "accept" "(setq selected (nth (atoi (get_tile \"tasks\")) ux-tasks))(done_dialog 1)")
      (action_tile "cancel" "(setq selected nil)(done_dialog 0)")
      (setq choice (start_dialog)) (unload_dialog dialog-id) (setq dialog-id nil)
      (if (/= choice 1) (setq selected nil)))
    (progn
      (if (> dialog-id 0) (unload_dialog dialog-id)) (setq dialog-id nil)
      (setq selected (TT:PromptNumberedRecord ux-tasks 'TT:UXTaskLabel "Choose a task"))))
  (if selected
    (if (or (not (nth 3 selected)) (TT:ProjectCurrent))
      (apply (cadr selected) nil)
      (princ "\nOpen a readable project through TTPROJECT before using this task.")))
  (princ))

(defun TT:UXTitle (kind)
  (cond ((eq kind 'PROJECT) "Project") ((eq kind 'PLANTS) "Planting Tools")
    ((eq kind 'DATA) "Plant Libraries") ((eq kind 'OUTPUT) "Schedules / Reports")
    ((eq kind 'CHECK) "Verify / Diagnostics") ((eq kind 'RECOVERY) "Recovery")
    ((member kind '(IRR STATION CONTROLLER)) "Irrigation Tools")
    ((eq kind 'LIGHT) "Lighting Tools") ((eq kind 'DETAIL) "Detail Tools")
    ((eq kind 'SITE) "Site / Reference") ((eq kind 'WORK) "Work Area Tools") (T "Tools")))
(defun TT:UXPlantData () (TT:UXMenu 'DATA))
T

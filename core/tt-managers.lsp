;;; Project record managers share browsing/editing mechanics, not domain identity.
(defun TT:ManagerConfig (kind)
  ;; section, identity key, visible code key, title, editable fields
  (cond
    ((eq kind 'WORK) '(WORK_AREAS WORK_AREA_ID NAME "Work Areas" ((NAME "Name" REQUIRED))))
    ((eq kind 'SITE) '(REFERENCE_NOTES NOTE_ID CODE "Reference Notes"
      ((CODE "Code" REQUIRED) (DESCRIPTION "Description" REQUIRED) (UNIT_COST "Unit cost" NONNEGATIVE) (DEPTH "Depth, drawing units" NONNEGATIVE))))
    ((eq kind 'DETAIL) '(DETAIL_LIBRARY DETAIL_ID NUMBER "Details"
      ((NUMBER "Detail number" REQUIRED) (TITLE "Title" REQUIRED) (CATEGORY "Category" TEXT) (KEYWORDS "Keywords" TEXT)
       (NOTES "Notes" TEXT) (SOURCE_FILE "Source DWG path" TEXT))))
    ((eq kind 'LIGHT) '(LIGHTING_PALETTE FIXTURE_ID CODE "Lighting Fixtures"
      ((CODE "Code" REQUIRED) (DESCRIPTION "Description" REQUIRED) (WATTAGE "Watts" NONNEGATIVE)
       (VOLTAGE "Volts" POSITIVE) (UNIT_COST "Unit cost" NONNEGATIVE) (SYMBOL "Symbol block" REQUIRED))))
    ((eq kind 'IRR) '(IRRIGATION_PALETTE EQUIPMENT_ID CODE "Irrigation Equipment"
      ((CODE "Code" REQUIRED) (DESCRIPTION "Description" REQUIRED) (FLOW_GPM "Flow, gpm" NONNEGATIVE)
       (PRESSURE_PSI "Required pressure, psi" NONNEGATIVE) (LOSS_PSI "Inline loss, psi" NONNEGATIVE)
       (RADIUS_FT "Radius, feet" NONNEGATIVE) (UNIT_COST "Unit cost" NONNEGATIVE))))
    ((eq kind 'STATION) '(IRRIGATION_STATIONS STATION_ID NAME "Stations"
      ((NAME "Station name" REQUIRED) (CONTROLLER "Controller name" TEXT) (OUTPUT "Controller output" INTEGER)
       (NOTES "Notes" TEXT))))
    ((eq kind 'CONTROLLER) '(IRRIGATION_CONTROLLERS CONTROLLER_ID NAME "Controllers"
      ((NAME "Controller name" REQUIRED) (CAPACITY "Station capacity" INTEGER) (DESCRIPTION "Description" TEXT))))))

(defun TT:ManagerLabel (record config / title)
  (setq title (TT:DataValue record 'DESCRIPTION))
  (if (null title) (setq title (TT:DataValue record 'TITLE)))
  (strcat (TT:UIValue (TT:DataValue record (nth 2 config)))
    (if title (strcat " | " (TT:UIValue title)) "")))

;;; DCL single-selection values are canonical zero-based integer strings.
;;; Reject blank, malformed, stale and overflowing values before calling NTH.
(defun TT:ManagerSelection (records selection / index)
  (if (and records (listp records) (eq (type selection) 'STR)
           (> (strlen selection) 0) (<= (strlen selection) 10)
           (not (wcmatch selection "*[~0-9]*"))
           (setq index (atoi selection)) (>= index 0)
           (= selection (itoa index)) (< index (length records)))
    (nth index records)))

(defun TT:ManagerSelected ()
  (if manager-visible
    (TT:ManagerSelection manager-visible (get_tile "records"))))

(defun TT:ManagerEmptyText (kind)
  (cond ((eq kind 'WORK) "No Work Areas yet. Add a closed boundary to organize objects and schedules.")
    ((eq kind 'SITE) "No reference notes yet. Add a note and choose geometry to describe.")
    ((eq kind 'DETAIL) "No project details yet. Add a detail or copy one through Library.")
    ((eq kind 'LIGHT) "No project fixtures yet. Add a sample fixture or copy one through Library.")
    ((eq kind 'IRR) "No project equipment yet. Add equipment before placing heads and drawing pipes.")
    ((eq kind 'STATION) "No stations yet. Add a station, then Assign its irrigation objects.")
    ((eq kind 'CONTROLLER) "No controllers yet. Add a controller and capacity, then configure Stations.")))

(defun TT:ManagerGuidance (kind)
  (cond ((eq kind 'WORK) "Work Areas organize explicit assignments. New placements inherit the active area.")
    ((eq kind 'LIGHT) "Project fixtures are editable copies. Built-in fixtures are fictional samples.")
    ((eq kind 'IRR) "Add equipment > Place > Stations > Pipes > Verify > Size. Built-in equipment is sample data.")
    ((eq kind 'DETAIL) "Project details are editable copies. Placement currently creates a sample frame.")
    ((eq kind 'STATION) "Select a station to assign objects. Edit sets controller and output; names are references.")
    ((eq kind 'CONTROLLER) "Set capacity here. Use Tools > Stations to assign controller outputs.")
    (T "Project-owned notes describe geometry. Tools provides callouts and schedules.")))

(defun TT:ManagerDetail (/ record path key)
  (setq record (TT:ManagerSelected)
    path (if record (TT:ProjectResourcePath (TT:DataValue record 'SOURCE_FILE))))
  (foreach key '("edit" "remove" "place" "highlight" "details")
    (mode_tile key (if (and manager-project record) 0 1)))
  (if (eq kind 'CONTROLLER) (progn (mode_tile "place" 1) (mode_tile "highlight" 1)))
  (set_tile "detail" (if record (TT:ManagerLabel record manager-config) "Select a record to enable its actions."))
  (set_tile "recordhint"
    (cond ((null record) "Add creates a project record. Search only filters this project's list.")
      ((eq kind 'STATION) (strcat "Controller: " (TT:UIValue (TT:DataValue record 'CONTROLLER))
        " | Output: " (TT:UIValue (TT:DataValue record 'OUTPUT))))
      ((eq kind 'CONTROLLER) (strcat "Capacity: " (TT:UIValue (TT:DataValue record 'CAPACITY)) " station outputs. Use Stations to assign them."))
      ((and path (/= path "")) (if (findfile path) "Source file available. Edit changes the project record only."
        "Original source file unavailable. Project record is kept; use Edit to relink it."))
      (T "Edits belong to this project. Library records are unchanged."))))

(defun TT:ManagerRefresh (/ record query text all index selected-index)
  (setq manager-project (TT:ProjectCurrent) manager-visible nil query (strcase (get_tile "query"))
    all (TT:ProjectValue manager-project (car manager-config)) index 0 selected-index 0)
  (foreach record all
    (setq text (strcase (strcat (TT:ManagerLabel record manager-config) " "
      (TT:UIValue (TT:DataValue record 'CATEGORY)) " " (TT:UIValue (TT:DataValue record 'KEYWORDS)))))
    (if (or (= query "") (vl-string-search query text)) (setq manager-visible (cons record manager-visible))))
  (setq manager-visible (reverse manager-visible))
  (start_list "records")
  (foreach record manager-visible
    (add_list (TT:ManagerLabel record manager-config))
    (if (equal selected-id (TT:DataValue record (cadr manager-config))) (setq selected-index index))
    (setq index (1+ index)))
  (end_list)
  (if manager-visible (set_tile "records" (itoa selected-index)))
  (foreach text '("add" "library" "area") (mode_tile text (if manager-project 0 1)))
  (mode_tile "library" (if (and manager-project (member kind '(DETAIL LIGHT IRR))) 0 1))
  (set_tile "context" (TT:UXProjectContext manager-project))
  (set_tile "workarea" (TT:UXAreaContext manager-project))
  (set_tile "scope" (strcat (itoa (length all)) " project records | " (itoa (length manager-visible)) " match this search"))
  (set_tile "status" (if manager-feedback manager-feedback
    (cond ((null manager-project) "Project cannot be read. Close this manager and use Home > Recovery.")
      ((null all) (TT:ManagerEmptyText kind))
      ((null manager-visible) "No matches in this project. Clear the search to see all project records.")
      (T "Select a record, then choose an action. Remove checks dependencies first."))))
  (TT:ManagerDetail))

(defun TT:ManagerIdentityInUse (record config items / id item used)
  (setq id (TT:DataValue record (cadr config)))
  (foreach item items
    (if (or (and (not (equal (cdr (assoc 'OBJECT_TYPE (cdr item))) "WORK_AREA"))
                 (equal id (cdr (assoc 'CATALOG_ID (cdr item)))))
            (equal id (cdr (assoc 'WORK_AREA_ID (cdr item))))) (setq used T)))
  used)

(defun TT:ManagerSaveRecord (kind record old / config project records key other collision controller stations station outputs)
  (setq config (TT:ManagerConfig kind) project (TT:ProjectCurrent)
        records (TT:ProjectValue project (car config)) key (nth 2 config))
  (foreach other records
    (if (and (not (equal (TT:DataValue other (cadr config)) (TT:DataValue record (cadr config))))
      (= (strcase (TT:UIValue (TT:DataValue other key))) (strcase (TT:UIValue (TT:DataValue record key))))) (setq collision T)))
  (cond
    ((null project) nil)
    (collision (princ (strcat "\n'" (TT:UIValue (TT:DataValue record key)) "' is already used in this project. Enter a distinct name or code.")) nil)
    ((and old (member kind '(STATION CONTROLLER)) (not (equal (TT:DataValue old 'NAME) (TT:DataValue record 'NAME))))
      (princ "\nStation/controller names are references. Create a new name and reassign its uses before removing the old record.") nil)
    ((and (eq kind 'STATION) (/= (TT:DataValue record 'CONTROLLER) "")
      (not (TT:StationAssignmentValid project record old))) nil)
    ((and (eq kind 'CONTROLLER) (not (TT:ControllerCapacityValid project record))) nil)
    (T (TT:ProjectSaveSection (car config) (if old (subst record old records) (append records (list record)))))))

(defun TT:StationAssignmentValid (project record old / controller station valid)
  (setq controller (TT:DataFindByValue (TT:ProjectValue project 'IRRIGATION_CONTROLLERS) 'NAME (TT:DataValue record 'CONTROLLER))
        valid (and controller (<= (TT:DataValue record 'OUTPUT) (TT:DataValue controller 'CAPACITY))))
  (foreach station (TT:ProjectValue project 'IRRIGATION_STATIONS)
    (if (and (not (equal station old)) (equal (TT:DataValue station 'CONTROLLER) (TT:DataValue record 'CONTROLLER))
             (equal (TT:DataValue station 'OUTPUT) (TT:DataValue record 'OUTPUT))) (setq valid nil)))
  (if (not valid) (princ "\nStation was not saved. Check the controller name, choose an unused output and stay within capacity."))
  valid)

(defun TT:ControllerCapacityValid (project record / station valid)
  (setq valid T)
  (foreach station (TT:ProjectValue project 'IRRIGATION_STATIONS)
    (if (and (equal (TT:DataValue station 'CONTROLLER) (TT:DataValue record 'NAME))
             (> (TT:DataValue station 'OUTPUT) (TT:DataValue record 'CAPACITY))) (setq valid nil)))
  (if (not valid) (princ "\nCapacity is below an assigned station output. Reassign that station first."))
  valid)

(defun TT:ManagerHighlight (kind record / config id item data count selected)
  (setq config (TT:ManagerConfig kind) id (TT:DataValue record (cadr config)) count 0 selected (ssadd))
  (foreach item (TT:ProjectItems (TT:SmartScan) (TT:ProjectCurrent))
    (setq data (cdr item))
    (if (or (equal id (cdr (assoc 'CATALOG_ID data))) (equal id (cdr (assoc 'WORK_AREA_ID data)))
      (and (eq kind 'STATION) (equal (TT:DataValue record 'NAME) (cdr (assoc 'STATION data)))))
      (progn (ssadd (car item) selected) (setq count (1+ count)))))
  (sssetfirst nil selected)
  (princ (strcat "\n" (itoa count) " matching objects selected for " (TT:ManagerLabel record config) ".")) count)

(defun TT:ManagerNamedDependencies (kind record project / item used name)
  (setq name (TT:DataValue record 'NAME))
  (if (eq kind 'CONTROLLER)
    (foreach item (TT:ProjectValue project 'IRRIGATION_STATIONS)
      (if (equal name (TT:DataValue item 'CONTROLLER)) (setq used T)))
    (foreach item (TT:ProjectItems (TT:SmartScan) project)
      (if (equal name (cdr (assoc 'STATION (cdr item)))) (setq used T))))
  used)

(defun TT:ManagerNew (kind / config record field)
  (setq config (TT:ManagerConfig kind) record (list (car config) (cons (cadr config) (TT:GenerateUUID))))
  (foreach field (nth 4 config)
    (setq record (TT:DataPut record (car field) (if (member (nth 2 field) '(INTEGER POSITIVE)) 1.0
      (if (eq (nth 2 field) 'NONNEGATIVE) 0.0 "")))))
  (setq record (TT:UIEditRecord record (nth 4 config) (strcat "TerraTools | " (nth 3 config))))
  (if record (TT:ManagerSaveRecord kind record nil)))

(defun TT:ManagerAction (kind action record / config project records edited answer item blocked old-data)
  (setq config (TT:ManagerConfig kind) project (TT:ProjectCurrent) records (TT:ProjectValue project (car config)))
  (cond
    ((= action 1)
      (cond ((eq kind 'WORK) (C:TTWORKAREA)) ((eq kind 'SITE) (C:TTREFNOTE))
        ((eq kind 'DETAIL) (TT:ManagerNew kind)) ((eq kind 'LIGHT) (TT:LightingPaletteAdd))
        ((eq kind 'IRR) (TT:IrrigationAdd)) (T (TT:ManagerNew kind))))
    ((and (= action 2) record)
      (setq edited (TT:UIEditRecord record (nth 4 config) (strcat "TerraTools | " (nth 3 config))))
      (if edited (TT:ManagerSaveRecord kind edited record)))
    ((and (= action 3) record)
      (setq blocked (TT:ManagerIdentityInUse record config (TT:SmartScan)))
      (if (member kind '(STATION CONTROLLER)) (setq blocked (TT:ManagerNamedDependencies kind record project)))
      (if blocked (princ "\nRemoval refused: resolve drawing or project dependencies first.")
        (progn
          (initget "Yes No") (setq answer (getkword (strcat "\nRemove " (TT:ManagerLabel record config) "? Check other project drawings first. [Yes/No] <No>: ")))
          (if (= answer "Yes")
            (progn
              (setq item (if (eq kind 'WORK) (TT:WorkAreaEntity (TT:DataValue record 'WORK_AREA_ID)))
                    old-data (if item (TT:GetEntityXData item)))
              (if (or (null item) (TT:RemoveEntityXData item))
                (if (not (TT:ProjectSaveSection (car config) (vl-remove record records)))
                  (progn
                    (if old-data (TT:SetEntityXData item old-data))
                    (TT:ProjectPrintError)))
                (princ "\nThe Work Area boundary could not be detached. Check its layer; the project record was kept.")))))))
    ((and (= action 4) record) (TT:ManagerPlace kind record))
    ((and (= action 5) record) (TT:ManagerHighlight kind record))
    ((= action 6) (TT:LibraryCommand kind))
    ((= action 7) (TT:UXMenu kind))
    ((= action 8) (C:TTACTIVEWORKAREA))
    ((and (= action 9) record) (TT:UIRecordDetails record))))

(defun TT:RecordManager (kind / *error* manager-config manager-project manager-visible manager-feedback dialog-id action selected selected-id query pair opened before after result)
  (defun *error* (message)
    (if (and dialog-id (> dialog-id 0)) (unload_dialog dialog-id))
    (TT:ReportError "Project manager" message))
  (setq manager-config (TT:ManagerConfig kind) manager-project (TT:ProjectCurrent) action 1 query "")
  (if (null manager-project) (progn
      (princ "\nNo readable project is open. Use TT > Project to create/open one, or Recovery to inspect a missing file.")
      (setq opened T))
    (while (> action 0)
      (setq dialog-id (load_dialog (TT:StorageJoinPath *TT:Root* "dialogs/terratools-records.dcl")))
      (if (and (> dialog-id 0) (new_dialog "terratools_records" dialog-id))
        (progn
          (setq opened T)
          (set_tile "title" (strcat "TerraTools | " (nth 3 manager-config)))
          (set_tile "guidance" (TT:ManagerGuidance kind))
          (set_tile "place" (if (member kind '(WORK SITE STATION)) "Assign..." "Place"))
          (set_tile "query" query) (TT:ManagerRefresh)
          (action_tile "search" "(setq manager-feedback nil)(TT:ManagerRefresh)")
          (action_tile "clear" "(set_tile \"query\" \"\")(setq manager-feedback nil)(TT:ManagerRefresh)")
          (action_tile "records" "(TT:ManagerDetail)")
          (foreach pair '(("add" . 1) ("edit" . 2) ("remove" . 3) ("place" . 4) ("highlight" . 5)
                          ("library" . 6) ("more" . 7) ("area" . 8) ("details" . 9))
            (action_tile (car pair) (strcat "(setq selected (TT:ManagerSelected) selected-id (TT:DataValue selected (cadr manager-config)) query (get_tile \"query\"))(done_dialog " (itoa (cdr pair)) ")")))
          (action_tile "cancel" "(done_dialog 0)")
          (setq action (start_dialog)) (unload_dialog dialog-id) (setq dialog-id nil)
          (if (> action 0)
            (progn
              (setq before (TT:ProjectValue (TT:ProjectCurrent) (car manager-config))
                result (TT:ManagerAction kind action selected)
                after (TT:ProjectValue (TT:ProjectCurrent) (car manager-config)))
              (setq manager-feedback
                (cond ((null (TT:ProjectCurrent)) "Project cannot be read. Use Home > Recovery; no replacement data was created.")
                  ((> (length after) (length before))
                    (strcat (itoa (- (length after) (length before))) " record(s) added to this project. Library records are unchanged."))
                  ((< (length after) (length before)) (strcat (TT:ManagerLabel selected manager-config) " removed from this project."))
                  ((not (equal after before)) (strcat (TT:ManagerLabel selected manager-config) " updated in this project."))
                  ((and (= action 4) (eq (type result) 'STR)) result)
                  ((and (= action 5) (numberp result)) (strcat (itoa result) " matching drawing objects selected."))
                  ((= action 8) (TT:UXAreaContext (TT:ProjectCurrent)))
                  ((member action '(1 2 3 6)) "No project record changes. If a save was refused, check the command-line explanation.")
                  (T "Ready. Your search and selected record are retained."))))))
        (progn (if (> dialog-id 0) (unload_dialog dialog-id)) (setq dialog-id nil action 0)))))
  opened)

(defun C:TTWORKAREAS () (if (not (TT:RecordManager 'WORK)) (C:TTWORKAREASCLI)) (princ))
(defun C:TTREFNOTES () (TT:RecordManager 'SITE) (princ))
(defun C:TTDETAILS () (if (not (TT:RecordManager 'DETAIL)) (C:TTDETAILSCLI)) (princ))
(defun C:TTLIGHTING () (if (not (TT:RecordManager 'LIGHT)) (C:TTLIGHTINGCLI)) (princ))
(defun C:TTIRRIGATION () (if (not (TT:RecordManager 'IRR)) (C:TTIRRIGATIONCLI)) (princ))
(defun C:TTSTATIONS () (TT:RecordManager 'STATION) (princ))
(defun C:TTCONTROLLERS () (TT:RecordManager 'CONTROLLER) (princ))
T

;;; TerraTools LT - Main DCL launcher and command-line module menus.

(setq *TT:UIModuleLoaded* T)

(defun TT:UIRunCommand (choice)
  (cond ((= choice 1) (TT:UXMenu 'PROJECT))
        ((= choice 2) (C:TTPREFERENCES))
        ((= choice 3) (C:TTWORKAREAS))
        ((= choice 4) (C:TTPLANTS))
        ((= choice 5) (TT:UXMenu 'SITE))
        ((= choice 6) (C:TTDETAILS))
        ((= choice 7) (C:TTLIGHTING))
        ((= choice 8) (C:TTIRRIGATION))
        ((= choice 9) (C:TTSCHEDULES))
        ((= choice 10) (C:TTDIAGNOSTICS))
        ((= choice 11) (C:TTABOUT))
        ((= choice 12) (C:TTSTANDARDS))
        ((= choice 13) (TT:UXMenu 'DATA))
        ((= choice 14) (C:TTHELP))
        ((= choice 15) (TT:UXMenu 'RECOVERY))
        ((= choice 16) (C:TTPACKAGE))))

(defun TT:MainDialog (/ *error* path dialog-id choice pair project opened unit)
  (defun *error* (message)
    (if (and dialog-id (> dialog-id 0)) (unload_dialog dialog-id))
    (TT:ReportError "Home" message))
  (setq path (TT:StorageJoinPath *TT:Root* "dialogs/terratools-main.dcl") choice 1)
  (while (> choice 0)
    (if (and (findfile path) (> (setq dialog-id (load_dialog path)) 0)
             (new_dialog "terratools_main" dialog-id))
      (progn
        (setq project (TT:ProjectCurrent) opened T unit (TT:DrawingUnitName))
        (set_tile "context" (TT:UXProjectContext project))
        (set_tile "units" (strcat "Drawing units: " (if unit (TT:UIValue unit) "Unresolved; review Project units")
          " | TerraTools " *TT:Version*))
        (set_tile "workarea" (TT:UXAreaContext project))
        (set_tile "database" (TT:UXDatabaseBanner (TT:PlantDatabaseManifest)))
        (set_tile "status" (if project "Choose a workflow. Return here after the task to continue."
          (if (TT:ProjectGetAssociation) "Project unavailable. Use Recovery to inspect the connection or open its file."
            "Welcome. Open Project to begin. Plant Library search is available now.")))
        (foreach pair '(("project" . 1) ("settings" . 2) ("workareas" . 3)
                        ("planting" . 4) ("site" . 5) ("details" . 6)
                        ("lighting" . 7) ("irrigation" . 8) ("schedules" . 9)
                        ("diagnostics" . 10) ("about" . 11)
                        ("standards" . 12) ("data" . 13) ("help" . 14)
                        ("recovery" . 15) ("package" . 16))
          (action_tile (car pair) (strcat "(done_dialog " (itoa (cdr pair)) ")")))
        (foreach pair '("settings" "workareas" "details" "lighting" "irrigation" "schedules" "standards")
          (mode_tile pair (if project 0 1)))
        (action_tile "close" "(done_dialog 0)")
        (setq choice (start_dialog)) (unload_dialog dialog-id) (setq dialog-id nil)
        (if (> choice 0) (TT:UIRunCommand choice)))
      (progn (if (and dialog-id (> dialog-id 0)) (unload_dialog dialog-id)) (setq dialog-id nil choice 0))))
  opened)

(defun C:TT (/ *error* option)
  (defun *error* (message) (TT:ReportError "TT" message))
  (if (not (TT:MainDialog))
    (progn
      (princ "\nThe TerraTools dialog could not be opened. Using the command-line launcher.")
      (initget "Project Planting WorkAreas Site Details Lighting Irrigation Schedules Settings Standards Data Recovery Package Diagnostics Help About")
      (setq option (getkword "\nTerraTools [Project/Planting/WorkAreas/Site/Details/Lighting/Irrigation/Schedules/Settings/Standards/Data/Recovery/Package/Diagnostics/Help/About]: "))
      (cond ((equal option "Project") (C:TTPROJECT))
            ((equal option "Planting") (C:TTPLANTS))
            ((equal option "WorkAreas") (C:TTWORKAREAS))
            ((equal option "Recovery") (TT:UXMenu 'RECOVERY))
            ((equal option "Package") (C:TTPACKAGE))
            ((equal option "Site") (C:TTSITE))
            ((equal option "Details") (C:TTDETAILS))
            ((equal option "Lighting") (C:TTLIGHTING))
            ((equal option "Irrigation") (C:TTIRRIGATION))
            ((equal option "Schedules") (C:TTSCHEDULES))
            ((equal option "Settings") (C:TTPREFERENCES))
            ((equal option "Standards") (C:TTSTANDARDS))
            ((equal option "Data") (C:TTPLANTDATA))
            ((equal option "Diagnostics") (C:TTDIAGNOSTICS))
            ((equal option "Help") (C:TTHELP))
            ((equal option "About") (C:TTABOUT)))))
  (princ))

(defun C:TERRATOOLS () (C:TT))

(defun C:TTPLANTING (/ option)
  (initget "Search Palette Place Path Array Random Areas Mix EditMix Labels Schedule Verify")
  (setq option (getkword "\nPlanting [Search/Palette/Place/Path/Array/Random/Areas/Mix/EditMix/Labels/Schedule/Verify] <Search>: "))
  (if (null option) (setq option "Search"))
  (cond ((equal option "Search") (C:TTPLANTSEARCH))
        ((equal option "Palette") (C:TTPLANTS))
        ((equal option "Place") (C:TTPLACEPLANT))
        ((equal option "Path") (C:TTPLANTPATH))
        ((equal option "Array") (C:TTPLANTARRAY))
        ((equal option "Random") (C:TTPLANTRANDOM))
        ((equal option "Areas") (C:TTGROUND))
        ((equal option "Mix") (C:TTMIX))
        ((equal option "EditMix") (C:TTMIXEDIT))
        ((equal option "Labels") (C:TTLABELGROUP))
        ((equal option "Schedule") (C:TTPLANTSCHEDULE))
        ((equal option "Verify") (C:TTVERIFYPLANTS)))
  (princ))

(defun C:TTSITE (/ option)
  (initget "Reference Area Length Volume Slope Bearing Coordinate Spot Concept Convert Schedule Callout UpdateCallouts")
  (setq option (getkword "\nSite [Reference/Area/Length/Volume/Slope/Bearing/Coordinate/Spot/Concept/Convert/Schedule/Callout/UpdateCallouts]: "))
  (cond ((equal option "Reference") (C:TTREFNOTES)) ((equal option "Area") (C:TTAREA))
        ((equal option "Length") (C:TTLENGTH)) ((equal option "Volume") (C:TTVOLUME))
        ((equal option "Slope") (C:TTSLOPE)) ((equal option "Coordinate") (C:TTCOORDLABEL))
        ((equal option "Bearing") (C:TTBEARINGDIST))
        ((equal option "Spot") (C:TTSPOTELEVATION)) ((equal option "Concept") (C:TTCONCEPT))
        ((equal option "Convert") (C:TTUNITCONVERT))
        ((equal option "Callout") (C:TTREFNOTELABEL))
        ((equal option "UpdateCallouts") (C:TTUPDATEREFNOTELABELS))
        ((equal option "Schedule") (C:TTREFNOTESCHEDULE)))
  (princ))

(defun C:TTSCHEDULES () (TT:UXMenu 'OUTPUT) (princ))
(defun C:TTDIAGNOSTICS () (TT:UXMenu 'CHECK) (princ))

(defun C:TTABOUT (/ project)
  (setq project (TT:ProjectCurrent))
  (princ (strcat "\nTerraTools LT " *TT:Version*
                 "\nTarget: AutoCAD LT 2024+ on Windows"
                 "\nProject: " (if project (TT:ProjectValue project 'PROJECT_NAME) "None")
                 "\nModules: Planting, Site, Details, Lighting, Irrigation, Schedules"))
  (princ))

T
